--
-- CDDL HEADER START
--
-- The contents of this file are subject to the terms of the
-- Common Development and Distribution License (the "License").
-- You may not use this file except in compliance with the License.
--
-- You can obtain a copy of the license at usr/src/OPENSOLARIS.LICENSE
-- or http://www.opensolaris.org/os/licensing.
-- See the License for the specific language governing permissions
-- and limitations under the License.
--
-- When distributing Covered Code, include this CDDL HEADER in each
-- file and include the License file at usr/src/OPENSOLARIS.LICENSE.
-- If applicable, add the following below this CDDL HEADER, with the
-- fields enclosed by brackets "[]" replaced with your own identifying
-- information: Portions Copyright [yyyy] [name of copyright owner]
--
-- CDDL HEADER END
--

--
-- Copyright (c) 2010, Oracle and/or its affiliates. All rights reserved.
-- Copyright 2018 Nexenta Systems, Inc.
--

SUN-IREPORT-MIB DEFINITIONS ::= BEGIN

IMPORTS
	products
		FROM SUN-MIB
	OBJECT-TYPE, NOTIFICATION-TYPE, MODULE-IDENTITY
		FROM SNMPv2-SMI
	TEXTUAL-CONVENTION, DateAndTime, DisplayString
		FROM SNMPv2-TC
	OBJECT-GROUP, NOTIFICATION-GROUP
		FROM SNMPv2-CONF;

sunIreportMIB MODULE-IDENTITY
	LAST-UPDATED	"201803120000Z"
	ORGANIZATION	"Nexenta Systems, Inc."
	CONTACT-INFO	"https://www.nexenta.com"
	DESCRIPTION
		"Copyright (c) 2010, Oracle and/or its affiliates. All rights reserved.
		Copyright 2018 Nexenta Systems, Inc.

		MIB providing access to Fault Management Informational Report Notifications."
	REVISION	"201803120000Z"
	DESCRIPTION	"Version: 1.1"
	::= { ireport 1 }

ireport OBJECT IDENTIFIER ::= { products 197 }

SunIreportSmfState ::= TEXTUAL-CONVENTION
	STATUS		current
	DESCRIPTION
		"Represents an SMF service state"
	SYNTAX	INTEGER {
		offline(0),
		online(1),
		degraded(2),
		disabled(3),
		maintenance(4),
		uninitialized(5)
	}

sunIreportNotification OBJECT IDENTIFIER ::= { sunIreportMIB 1 }

sunIreportHostname OBJECT-TYPE
	SYNTAX		DisplayString
	MAX-ACCESS	accessible-for-notify
	STATUS		current
	DESCRIPTION
		"Hostname of the system on which the event occurred"
	::= { sunIreportNotification 1 }

sunIreportMsgid OBJECT-TYPE
	SYNTAX		DisplayString
	MAX-ACCESS	accessible-for-notify
	STATUS		current
	DESCRIPTION
		"Message ID of Knowledge Article associated with this event"
	::= { sunIreportNotification 2 }

sunIreportSeverity OBJECT-TYPE
	SYNTAX		DisplayString
	MAX-ACCESS	accessible-for-notify
	STATUS		current
	DESCRIPTION
		"Severity of the event"
	::= { sunIreportNotification 3 }

sunIreportDescription OBJECT-TYPE
	SYNTAX		DisplayString
	MAX-ACCESS	accessible-for-notify
	STATUS		current
	DESCRIPTION
		"Description of the event"
	::= { sunIreportNotification 4 }

sunIreportTime OBJECT-TYPE
	SYNTAX		DateAndTime
	MAX-ACCESS	accessible-for-notify
	STATUS		current
	DESCRIPTION
		"Timestamp of the event"
	::= { sunIreportNotification 5 }

sunIreportSmfFMRI OBJECT-TYPE
	SYNTAX		DisplayString
	MAX-ACCESS	accessible-for-notify
	STATUS		current
	DESCRIPTION
		"FMRI of the SMF service asssociated with this event"
	::= { sunIreportNotification 6 }

sunIreportSmfFromState OBJECT-TYPE
	SYNTAX		SunIreportSmfState
	MAX-ACCESS	accessible-for-notify
	STATUS		current
	DESCRIPTION
		"Previous state of the service that transitioned"
	::= { sunIreportNotification 7 }

sunIreportSmfToState OBJECT-TYPE
	SYNTAX		SunIreportSmfState
	MAX-ACCESS	accessible-for-notify
	STATUS		current
	DESCRIPTION
		"Final state of the service that transitioned"
	::= { sunIreportNotification 8 }

sunIreportSmfTransitionReason OBJECT-TYPE
	SYNTAX		DisplayString
	MAX-ACCESS	accessible-for-notify
	STATUS		current
	DESCRIPTION
		"Reason for the state transition"
	::= { sunIreportNotification 9 }

--
-- RFC 3584 requires that the next-to-last sub-ID be zero to allow for
-- mapping v2/v3 notifications to v1 traps.
--

sunIreportTraps OBJECT IDENTIFIER ::= { sunIreportMIB 2 0 }

sunIreportTrap NOTIFICATION-TYPE
	OBJECTS	{
		sunIreportHostname,
		sunIreportMsgid,
		sunIreportSeverity,
		sunIreportDescription,
		sunIreportTime,
		sunIreportSmfFMRI,
		sunIreportSmfFromState,
		sunIreportSmfToState,
		sunIreportSmfTransitionReason
	}
	STATUS	current
	DESCRIPTION
		"Trap notification that a informational report has occurred.

		The last four entries in the trap will only be set for SMF
		service state transition (STN) events.  The following values for
		sunIreportMsgid correspond to an STN event:

		SMF-8000-SR
		SMF-8000-TC
		SMF-8000-UQ
		SMF-8000-VE
		SMF-8000-WJ
		SMF-8000-X2"

	::= { sunIreportTraps 1 }

END
