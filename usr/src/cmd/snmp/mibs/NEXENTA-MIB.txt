--
-- This file and its contents are supplied under the terms of the
-- Common Development and Distribution License ("CDDL"), version 1.0.
-- You may only use this file in accordance with the terms of version
-- 1.0 of the CDDL.
--
-- A full copy of the text of the CDDL should have accompanied this
-- source.  A copy of the CDDL is also available via the Internet at
-- http://www.illumos.org/license/CDDL.
--

-- Copyright 2019 Nexenta by DDN, Inc.  All rights reserved.

---------------------------------------------------------------
-- Nexenta base MIB
---------------------------------------------------------------

NEXENTA-MIB DEFINITIONS ::= BEGIN

IMPORTS
	enterprises, MODULE-IDENTITY FROM SNMPv2-SMI;

nexentaMIB MODULE-IDENTITY
	LAST-UPDATED	"202110220000Z"
	ORGANIZATION	"Tintri by DDN, Inc."
	CONTACT-INFO	"Support"
	DESCRIPTION	"MIB that defines the Nexenta enterprise"
	REVISION	"202110220000Z"
	DESCRIPTION	""
	::= { enterprises 40045 }

core OBJECT IDENTIFIER ::= { nexentaMIB 1 }

storage OBJECT IDENTIFIER ::= { core 1 }

zfs OBJECT IDENTIFIER ::= { storage 1 }
ssm OBJECT IDENTIFIER ::= { storage 2 }
fen OBJECT IDENTIFIER ::= { storage 3 }

nexentaNef OBJECT IDENTIFIER ::= { nexentaMIB 100 }

END
