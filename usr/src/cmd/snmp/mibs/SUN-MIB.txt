--
-- Copyright (c) 2003, 2011, Oracle and/or its affiliates. All rights reserved.
--
-- U.S. Government Rights - Commercial software. Government users are subject to
-- the Sun Microsystems, Inc. standard license agreement and applicable
-- provisions of the FAR and its supplements.
--
--
-- This distribution may include materials developed by third parties. Sun, Sun
-- Microsystems, the Sun logo and Solaris are trademarks or registered
-- trademarks of Sun Microsystems, Inc. in the U.S. and other countries.
--
--

---------------------------------------------------------------
-- Systems Management Agent (SMA) SUN Enterprise definition MIB
---------------------------------------------------------------

SUN-MIB DEFINITIONS ::= BEGIN

IMPORTS
	enterprises, MODULE-IDENTITY FROM SNMPv2-SMI;

sunMIB MODULE-IDENTITY
	LAST-UPDATED	"200309180000Z"
	ORGANIZATION	"Sun Microsystems, Inc."
	CONTACT-INFO	"Customer support"
	DESCRIPTION	"MIB that defines the Sun enterprise"
	::= { enterprises 42 }

sun OBJECT IDENTIFIER ::= { enterprises 42 }
products OBJECT IDENTIFIER ::= { sun 2 }
management OBJECT IDENTIFIER ::= { products 2 }
sma OBJECT IDENTIFIER ::= { management 4 }

END
